FME workspace fme_droga.fmw

Parameters:
- DestDataset_GEOJSON = $(FME_MF_DIR)results\output.json   # Destination GeoJSON File
- SourceDataset_CSV2 = $(FME_MF_DIR)wsp.csv   # Source CSV (Comma Separated Value) File(s)
- SourceDataset_SHAPEFILE = $(FME_MF_DIR)T2019_KAR_POI_TABLE.shp   # Source Esri Shapefile(s)
- FEATURE_TYPES =
- SourceDataset_SHAPEFILE_4 = $(FME_MF_DIR)T2019_KAR_STREET_NODE.shp   # Source Esri Shapefile(s)
- FEATURE_TYPES_2 = T2019_KAR_STREET_NODE
- SourceDataset_SHAPEFILE_5 = $(FME_MF_DIR)T2019_KAR_STREETS.shp   # Source Esri Shapefile(s)
- FEATURE_TYPES_3 =
- DestDataset_GEODATABASE_FILE = $(FME_MF_DIR)results\wyniki.gdb   # File Geodatabase

Readers:
- CSV2_1: CSV2 from $(SourceDataset_CSV2) in LL-WGS84
- SHAPEFILE_1: SHAPEFILE from $(SourceDataset_SHAPEFILE) in LL-WGS84
- SHAPEFILE_2: SHAPEFILE from $(SourceDataset_SHAPEFILE_4) in LL-WGS84
- SHAPEFILE_3: SHAPEFILE from $(SourceDataset_SHAPEFILE_5) in LL-WGS84

Writers:
- GEOJSON_1: GEOJSON to $(DestDataset_GEOJSON)
- GEODATABASE_FILE_1: GEODATABASE_FILE to $(DestDataset_GEODATABASE_FILE) in DHDN.Berlin/Cassini

T2019_KAR_POI_TABLE (reader SHAPEFILE_1)
    attributes: POI_ID long, LINK_ID long, TYPE char(250), POI_NAME char(250), ST_NAME char(250), LAT double, LON double
    -> Reprojector_3
Reprojector_3
    DEST = DHDN.Berlin/Cassini
    INTERPOLATION_TYPE_NAME = Nearest Neighbor
    RASTER_CELL_SIZE = Preserve Cells
    RASTER_TOLERANCE = 0.0
    SOURCE = LL-WGS84
    REPROJECTED -> punkty_z_kosztami [BASE]
    REPROJECTED -> punkty_bez_kosztów [BASE]
T2019_KAR_STREETS (reader SHAPEFILE_3)
    attributes: LINK_ID long, ST_NAME char(254), REF_IN_ID long, NREF_IN_ID long, FUNC_CLASS char(1), SPEED_CAT char(1), FR_SPEED_L long, TO_SPEED_L long, DIR_TRAVEL char(1)
    -> Reprojector_4
Reprojector_4
    DEST = DHDN.Berlin/Cassini
    INTERPOLATION_TYPE_NAME = Nearest Neighbor
    RASTER_CELL_SIZE = Preserve Cells
    RASTER_TOLERANCE = 0.0
    SOURCE = LL-WGS84
    REPROJECTED -> shortest_way_without_any_conditions [NETWORK]
    REPROJECTED -> Tester
Tester
    BOOL_OP = OR
    COMPOSITE_TEST = 1
    TEST_CLAUSE = TEST @Value(DIR_TRAVEL) = Y
    TEST_MODE = TEST
    PASSED -> AttributeManager
    FAILED -> AddBothAtt
AttributeManager
    ATTR_TABLE:
      SET_TO Forward = 1
      SET_TO Reverse = 9999
    -> Shortest_way_with_costs [NETWORK]
AddBothAtt: AttributeManager
    ATTR_TABLE:
      SET_TO Forward = 1
      SET_TO Reverse = 1
    -> Shortest_way_with_costs [NETWORK]
CSV (reader CSV2_1)
    attributes: x x_coordinate, y y_coordinate
    -> VertexCreator
VertexCreator
    MEASURE_TYPE = Continuous
    MISSING_VAL_MODE = Compute
    MODE_NAME = Add Point
    XVAL = @Value(x)
    YVAL = @Value(y)
    -> LineBuilder
LineBuilder
    ACCUM_INPUT_ATTRS = Use Attributes From One Feature
    GROUP_BY = fme_feature_type
    REMOVE_DUPLICATES = No
    LINE -> Reprojector_2
Reprojector_2
    DEST = DHDN.Berlin/Cassini
    INTERPOLATION_TYPE_NAME = Nearest Neighbor
    RASTER_CELL_SIZE = Preserve Cells
    RASTER_TOLERANCE = 0.0
    SOURCE = LL-WGS84
    REPROJECTED -> shortest_way_without_any_conditions [FROM-TO]
    REPROJECTED -> Shortest_way_with_costs [FROM-TO]
Shortest_way_with_costs: ShortestPathFinder
    ALLOW_UTURNS = Yes
    REORDER_CHOICE = None
    SNAP_POINTS = Yes
    SNAP_TOLERANCE = 200
    WEIGHT_ATTR_1 = Forward
    WEIGHT_ATTR_2 = Reverse
    WEIGHT_ATTR_CHOICE = By Two Attributes
    PATH -> punkty_z_kosztami [CANDIDATE]
    PATH -> LineOnLineOverlayer [LINE]
punkty_z_kosztami: NeighborFinder
    CANDIDATES_FIRST = No
    INSERT_VERTEX = No
    K = 4000
    MAX = 5
    MEASURES_FROM_CANDIDATE = Yes
    MEASURE_TYPE = Continuous
    MODE = Bases and Candidates
    TREAT_POLYGON_AS = Lines
    MATCHED -> punkty (writer GEOJSON_1)
shortest_way_without_any_conditions: ShortestPathFinder
    ALLOW_UTURNS = Yes
    REORDER_CHOICE = None
    SNAP_POINTS = No
    WEIGHT_ATTR_CHOICE = By Length
    PATH -> punkty_bez_kosztów [CANDIDATE]
    PATH -> LineOnLineOverlayer [LINE]
punkty_bez_kosztów: NeighborFinder
    CANDIDATES_FIRST = No
    INSERT_VERTEX = No
    K = 4000
    MAX = 5
    MEASURES_FROM_CANDIDATE = Yes
    MEASURE_TYPE = Continuous
    MODE = Bases and Candidates
    TREAT_POLYGON_AS = Lines
    MATCHED -> punkty (writer GEOJSON_1)
punkty (writer GEOJSON_1)
    attributes: POI_ID int, LINK_ID int, TYPE string, POI_NAME string, ST_NAME string, LAT float, LON float
LineOnLineOverlayer
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    POINT -> T2019_KAR_STREET_NODE (writer GEODATABASE_FILE_1)
T2019_KAR_STREET_NODE (writer GEODATABASE_FILE_1)
    attributes: NODE_ID integer, LINK_ID integer, POINT_NUM integer, Z_LEVEL integer, INTERSECT char(1), LAT double, LON double
T2019_KAR_STREET_NODE (reader SHAPEFILE_2)
    attributes: NODE_ID long, LINK_ID long, POINT_NUM long, Z_LEVEL long, INTERSECT char(1), LAT double, LON double
    -> Reprojector
Reprojector
    DEST = DHDN.Berlin/Cassini
    INTERPOLATION_TYPE_NAME = Nearest Neighbor
    RASTER_CELL_SIZE = Preserve Cells
    RASTER_TOLERANCE = 0.0
    SOURCE = LL-WGS84
